module openconfig-test-xfmr-action {

  yang-version "1.1";

  namespace "http://openconfig.net/yang/test-xmfr-action";
  prefix "oc-test-xfmr-act";

  organization "OpenConfig working group";
  contact "OpenConfig working group www.openconfig.net";

  description
    "YANG 1.1 action test model. Defines action callbacks for the
    transformer action infrastructure tests, kept separate from the
    yang-version 1 openconfig-test-xfmr model.";

  revision "2026-04-20" {
    description "Initial revision.";
  }

  container test-xfmr-action {
    description "Top-level container for action infrastructure tests.";

    container test-sensor-groups {
      list test-sensor-group {
        key "id";

        leaf id {
          type string;
        }

        action test-sensor-reset {
          description "Reset a test sensor group.";
          input {
            leaf level {
              type uint32;
              description "Reset level (0=soft, 1=hard).";
            }
          }
          output {
            leaf status {
              type string;
              description "Reset operation status.";
            }
            leaf message {
              type string;
              description "Detailed result message.";
            }
          }
        }

        action test-sensor-status {
          description "Query sensor group status without any input.";
          output {
            leaf status {
              type string;
              description "Current sensor group status.";
            }
          }
        }

        action test-sensor-clear {
          description "Clear sensor data; fire-and-forget with no output.";
          input {
            leaf reason {
              type string;
              description "Reason for clearing sensor data.";
            }
          }
        }

        action test-sensor-configure {
          description "Reconfigure sensor with multiple parameters.";
          input {
            leaf mode {
              type string;
              description "Sensor operating mode.";
            }
            leaf interval {
              type uint32;
              description "Polling interval in seconds.";
            }
            leaf enabled {
              type boolean;
              description "Whether the sensor is enabled.";
            }
          }
          output {
            leaf result {
              type string;
              description "Configuration result.";
            }
            leaf applied-mode {
              type string;
              description "The mode that was applied.";
            }
            leaf applied-interval {
              type uint32;
              description "The interval that was applied.";
            }
          }
        }
      }
    }

    container global-sensor {
      action test-global-reset {
        description "Reset global sensor; container-level action with no list key.";
        input {
          leaf force {
            type boolean;
            description "Whether to force the reset.";
          }
        }
        output {
          leaf status {
            type string;
            description "Reset operation status.";
          }
          leaf message {
            type string;
            description "Detailed result message.";
          }
        }
      }
    }
  }
}

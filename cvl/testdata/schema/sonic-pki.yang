module sonic-pki {
    namespace "http://github.com/sonic-net/sonic-pki";
    prefix sonic-pki;
    yang-version 1.1;

    organization
        "SONiC";

    contact
        "SONiC";

    description
        "SONIC PKI YANG";

    revision 2024-01-30 {
        description
            "Add vrf-name attribute";
    }
    revision 2023-01-10 {
        description
            "Add validations";
    }
    revision 2022-09-30 {
        description
            "Initial revision.";
    }

    container sonic-pki {
        container SECURITY_PROFILES {
            list SECURITY_PROFILES_LIST {
                key "profile-name";
                leaf "profile-name" {
                    type string;
                    description
                        "Unique name for the security profile";
                }
                leaf "certificate-name" {
                    type string;
                    description
                        "Certificate file name";
                }
            }
        }
    }
}

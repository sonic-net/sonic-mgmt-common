module sonic-acl {
	namespace "http://github.com/Azure/sonic-acl";
	prefix sacl;
	yang-version 1.1;

	import ietf-inet-types {
		prefix inet;
	}

	import sonic-common {
		prefix cmn;
	}

	import sonic-extension {
		prefix sonic-ext;
	}

	import sonic-port {
		prefix prt;
	}

    import sonic-portchannel {
        prefix po;
    }

	import sonic-mirror-session {
		prefix sms;
	}

	organization
		"SONiC";

	contact
		"SONiC";

	description
		"SONIC ACL";

	revision 2019-05-15 {
		description
			"Initial revision.";
	}

	container sonic-acl {

		container ACL_TABLE {

			list ACL_TABLE_LIST {
				key "aclname";
				max-elements 1024; // Max 1K ACL tables for all platforms

				leaf aclname {
					type string {
						pattern '[a-zA-Z0-9]{1}([-a-zA-Z0-9_]{0,71})';
						length 1..72;
					}
				}

				leaf policy_desc {
					type string {
						length 1..255 {
							error-app-tag policy-desc-invalid-length;
						}
					}
				}

				leaf stage {
					type enumeration {
						enum INGRESS;
						enum EGRESS;
					}
				}

				leaf type {
					type enumeration {
						enum MIRROR;
						enum L2;
						enum L3;
						enum L3V6;
					}
				}

				leaf-list ports {
                    type union {
                        type leafref {
                            path "/prt:sonic-port/prt:PORT/prt:PORT_LIST/prt:ifname";
                        }
                        type leafref {
                            path "/po:sonic-portchannel/po:PORTCHANNEL/po:PORTCHANNEL_LIST/po:name";
                        }
                    }
				}
			}
		}

		container ACL_RULE {

			list ACL_RULE_LIST { 
				key "aclname rulename";
				//sonic-ext:custom-validation ValidateMaxAclRule; // Max 64K ACL rules for all platforms

				leaf aclname {
					type leafref {
						path "../../../ACL_TABLE/ACL_TABLE_LIST/aclname";
					}
					must "(/cmn:operation/cmn:operation != 'DELETE') or " +
						"count(current()/../../../ACL_TABLE/ACL_TABLE_LIST[aclname=current()]/ports) = 0" {
							error-message "Ports are already bound to this rule.";
						}
				} 

				leaf rulename {
					type string;
				}

				leaf PRIORITY {
					type uint16 {
						range "1..65535"{
							error-message "Invalid ACL rule priority.";
					}
					}
				}

				leaf RULE_DESCRIPTION {
					type string;
				}

				leaf PACKET_ACTION {
					type enumeration {
						enum FORWARD;
						enum DROP;
						enum REDIRECT;
						enum INT_INSERT;
						enum INT_DELETE;
					}
				}

				leaf MIRROR_ACTION {
					type leafref {
						path "/sms:sonic-mirror-session/sms:MIRROR_SESSION/sms:MIRROR_SESSION_LIST/sms:name";
					}
				}

				leaf IP_TYPE {
					//sonic-ext:custom-validation ValidateAclRuleIPAddress;
					type enumeration {
						enum ANY;
						enum IP;
						enum IPV4;
						enum IPV4ANY;
						enum NON_IPV4;
						enum IPV6;
						enum IPV6ANY;
						enum NON_IPV6;
					}

					default IPV4;
				}

				leaf IP_PROTOCOL {
					type uint8 {
						range "1|2|6|17|46|47|51|103|115";
					}
				}

				leaf ETHER_TYPE {
					type string {
						pattern "(0x88CC)|(0x8100)|(0x8915)|(0x0806)|(0x0800)|(0x86DD)|(0x8847)" {
							error-message "Invalid ACL Rule Ether Type";
							error-app-tag ether-type-invalid;
						}
					}
				}

				choice ip_src_dst {
					case ipv4_src_dst {
						when "boolean(IP_TYPE[.='ANY' or .='IP' or .='IPV4' or .='IPV4ANY'])";
						leaf SRC_IP {
							mandatory true;
							type inet:ipv4-prefix;
						}
						leaf DST_IP {
							mandatory true;
							type inet:ipv4-prefix;
						}
					}
					case ipv6_src_dst {
						when "boolean(IP_TYPE[.='ANY' or .='IP' or .='IPV6' or .='IPV6ANY'])";
						leaf SRC_IPV6 {
							mandatory true;
							type inet:ipv6-prefix;    
						}
						leaf DST_IPV6 {
							mandatory true;
							type inet:ipv6-prefix;    
						}
					}
				}

				choice src_port {
					case l4_src_port {
						leaf L4_SRC_PORT {
							type uint16;
						}
					}
					case l4_src_port_range {
						leaf L4_SRC_PORT_RANGE {
							type string {
								pattern "[0-9]{1,5}(-)[0-9]{1,5}";
							}
						}
					}
				}

				choice dst_port {
					case l4_dst_port {
						leaf L4_DST_PORT {
							type uint16;
						}
					}
					case l4_dst_port_range {
						leaf L4_DST_PORT_RANGE {
							type string {
								pattern "[0-9]{1,5}(-)[0-9]{1,5}";
							}
						}
					}
				}

				leaf TCP_FLAGS { 
					type string {
						pattern "0[xX][0-9a-fA-F]{2}[/]0[xX][0-9a-fA-F]{2}";
					}
				}

				leaf DSCP { 
					type uint8;
				}
			}
		}
	}
}

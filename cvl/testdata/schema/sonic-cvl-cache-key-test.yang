module sonic-cvl-cache-key-test {
    namespace "http://github.com/sonic-net/sonic-cvl-cache-key-test";
    prefix cktest;
    yang-version 1.1;

    organization
        "SONiC";

    contact
        "SONiC";

    description
        "Test schema for regression coverage of requestCache keying when the
        Redis table name differs from the generated YANG list name (singleton
        container auto-converted to a list by generate_yin.py). Should not be
        used in production.";

    revision 2026-08-22 {
        description
            "Initial revision.";
    }

    container sonic-cvl-cache-key-test {
        container CACHE_KEY_TEST {
            container GLOBAL {
                leaf format {
                    type enumeration {
                        enum standard;
                        enum welf;
                    }
                    default standard;
                }

                leaf welf_firewall_name {
                    type string;
                    must "../format = 'welf'" {
                        error-message
                            "welf_firewall_name requires format=welf";
                    }
                }
            }
        }
    }
}

module sonic-security-global {
    namespace "http://github.com/sonic-net/sonic-security-global";
    prefix sonic-security;
    yang-version 1.1;

    import sonic-pki {
        prefix spki;
    }

    organization
        "SONiC";

    contact
        "SONiC";

    description
        "This module defines the global security configuration for SONiC.";

    revision 2024-07-03 {
        description
            "Initial revision.";
        reference
            "RFC XXXX";
    }

    container sonic-security-global {
        container SECURITY_GLOBAL {
            container global {
                leaf security_profile {
                    type leafref {
                        path "/spki:sonic-pki/spki:SECURITY_PROFILES/spki:SECURITY_PROFILES_LIST/spki:profile-name";
                    }
                    description
                        "Reference to the security profile defined in the sonic-pki module.";
                }
            }
        }
    }
}

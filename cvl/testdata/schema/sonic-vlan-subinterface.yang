module sonic-vlan-subinterface {
    namespace "http://github.com/Azure/sonic-vlan-subinterface";
    prefix svlansub;
    yang-version 1.1;

    organization
        "SONiC";

    contact
        "SONiC";

    description
        "SONIC SUN INTERFACE VLAN";

    revision 2024-03-10 {
        description
            "Initial revision.";
    }

    container sonic-vlan-subinterface {
        container VLAN_SUB_INTERFACE {
            list VLAN_SUB_INTERFACE_LIST {
                key "id";

                leaf id {
                    type string {
                        pattern '(Eth([1-3][0-9]{3}|[1-9][0-9]{2}|[1-9][0-9]|[0-9])' +
                        '|Eth([1-9]/(([1-9][0-9]|[1-9])|([1-9][0-9]|[1-9])/([1-9][0-9]|[1-9])))' +
                        '|Po([1-9]|[1-9][0-9]|1[0-9][0-9]|2[0-4][0-9]|25[0-6])' +
                        '|PortChannel([1-9]|[1-9][0-9]|1[0-9][0-9]|2[0-4][0-9]|25[0-6]))\.' +
                        '(6553[0-5]|655[0-2][0-9]|654[0-9]{2}|65[0-4][0-9]{2}|6[0-4][0-9]{3}|[1-5][0-9]{4}|[1-9][0-9]{1,3}|[0-9])' {
                            error-message "Invalid sub-interface name";
                            error-app-tag interface-name-invalid;
                        }
                    }
                }
            }
            list VLAN_SUB_INTERFACE_IPADDR_LIST {
                key "id";
                leaf id {
                    type leafref {
                        path "/svlansub:sonic-vlan-subinterface/svlansub:VLAN_SUB_INTERFACE/svlansub:VLAN_SUB_INTERFACE_LIST/svlansub:id";
                    }
                }
            }
        }
    }
}

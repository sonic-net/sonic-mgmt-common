module sonic-buffer-pg {
	namespace "http://github.com/Azure/sonic-buffer-pg";
	prefix bpg;

	import sonic-extension {
		prefix sonic-ext;
	}

	import sonic-port {
		prefix prt;
	}

	import sonic-buffer-profile {
		prefix bpf;
	}

	organization
		"SONiC";

	contact
		"SONiC";

	description
		"SONIC BUFFER PG";

	revision 2019-05-15 {
		description
			"Initial revision.";
	}


	container sonic-buffer-pg {

		container BUFFER_PG {

			list BUFFER_PG_LIST {
				key "ifname pg_num";
				sonic-ext:key-pattern "BUFFER_PG|{ifname}|{pg_num}"; //special pattern used for extracting keys from
				//redis-key and fill populate the yang instance
				// Total list instance = number(key1) * number(key2) * number(key3)

				leaf ifname {
					type leafref {
						path "/prt:sonic-port/prt:PORT/prt:PORT_LIST/prt:ifname";
					}
				}

				leaf pg_num {
					type string {
						pattern "[0-7]((-)[0-7])?" {
							error-message "Invalid Buffer PG number";
							error-app-tag pg-num-invalid;
						}
					}
				}

				leaf profile { //Hash reference key
					type leafref {
						path "/bpf:sonic-buffer-profile/bpf:BUFFER_PROFILE/bpf:BUFFER_PROFILE_LIST/bpf:name";
					}
				}

			}
		}
	}
}

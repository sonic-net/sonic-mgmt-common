module openconfig-sampling-sflow-annot {

    yang-version "1";

    namespace "http://openconfig.net/yang/annotation/oc-sampling-sflow-annot";
    prefix "oc-sampling-annot";

    import openconfig-extensions { prefix oc-ext; }
    import openconfig-sampling-sflow { prefix oc-sampling; }
    import sonic-extensions { prefix sonic-ext; }

    deviation /oc-sampling:sampling/oc-sampling:sflow {
      deviate add {
        sonic-ext:subtree-transformer "sflow_xfmr";
      }
    }


    deviation /oc-sampling:sampling/oc-sampling:sflow/oc-sampling:collectors {
      deviate add {
        sonic-ext:subtree-transformer "sflow_collector_xfmr";
        sonic-ext:path-transformer "sflow_collector_path_xfmr";
      }
    }


    deviation /oc-sampling:sampling/oc-sampling:sflow/oc-sampling:interfaces {
      deviate add {
        sonic-ext:subtree-transformer "sflow_interface_xfmr";
        sonic-ext:path-transformer "sflow_interface_path_xfmr";
      }
    }
}

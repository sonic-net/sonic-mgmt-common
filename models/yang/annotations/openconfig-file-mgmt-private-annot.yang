module openconfig-file-mgmt-private-annot {

    yang-version "1.1";

    namespace "http://openconfig.net/yang/file-mgmt-private-annot";
    prefix "oc-file-mgmt-private-annot";

    import sonic-extensions {
        prefix sonic-ext;
    }

    import openconfig-file-mgmt-private {
        prefix oc-file-mgmt-private;
    }

    deviation /oc-file-mgmt-private:copy {
        deviate add {
            sonic-ext:rpc-callback "rpc_copy_cb";
        }
    }
}

module openconfig-system-deviation {
  yang-version "1";
  namespace "http://openconfig.net/yang/system/deviation";
  prefix "oc-sys-deviate";

  import openconfig-extensions { prefix oc-ext; }

  import openconfig-system { prefix oc-sys; }

  import openconfig-system-utilization { prefix oc-sys-util; }

  import openconfig-hashing { prefix oc-hash; }

  import openconfig-system-bootz { prefix oc-sys-bootz; }

  import openconfig-interfaces { prefix oc-intf; }

  organization "SONiC Manageability";
  contact "SONiC";

  description
    "Deviations for openconfig-system model.";

  oc-ext:openconfig-version "0.5.0";

  revision "2024-09-20" {
    description
      "Adding support for AAA - authentication,authorization & accounting login method";
    reference
      "0.5.0";
  }

  revision "2024-09-13" {
    description
      "Adding support for dns container";
    reference
      "0.4.0";
  }

  revision "2024-09-02" {
    description
      "Added support for ntp container";
    reference
      "0.3.0";
  }

  revision "2024-08-12" {
    description
      "Added support for login,motd banners & timezone";
    reference
      "0.2.0";
  }

  revision "2024-05-02" {
    description
      "Initial version";
    reference
      "0.1.0";
  }


  deviation /oc-sys:system/oc-sys:config/oc-sys:domain-name {
    deviate not-supported;
  }

  deviation /oc-sys:system/oc-sys:state/oc-sys:domain-name {
    deviate not-supported;
  }

  deviation /oc-sys:system/oc-sys:state/oc-sys:last-configuration-timestamp {
    deviate not-supported;
  }

  deviation /oc-sys:system/oc-sys:processes/oc-sys:process/oc-sys:state/oc-sys:start-time {
    deviate not-supported;
  }

  deviation /oc-sys:system/oc-sys:processes/oc-sys:process/oc-sys:state/oc-sys:cpu-usage-user {
    deviate not-supported;
  }

  deviation /oc-sys:system/oc-sys:processes/oc-sys:process/oc-sys:state/oc-sys:cpu-usage-system {
    deviate not-supported;
  }

  deviation /oc-sys:system/oc-sys:processes/oc-sys:process/oc-sys:state/oc-sys:memory-usage {
    deviate not-supported;
  }

  deviation /oc-sys:system/oc-sys:ssh-server/oc-sys:config/oc-sys:enable {
    deviate not-supported;
  }

  deviation /oc-sys:system/oc-sys:ssh-server/oc-sys:config/oc-sys:protocol-version {
    deviate not-supported;
  }

  deviation /oc-sys:system/oc-sys:ssh-server/oc-sys:config/oc-sys:rate-limit {
    deviate not-supported;
  }

  deviation /oc-sys:system/oc-sys:ssh-server/oc-sys:config/oc-sys:session-limit {
    deviate not-supported;
  }

  deviation /oc-sys:system/oc-sys:telnet-server {
    deviate not-supported;
  }

  deviation /oc-sys:system/oc-sys:logging/oc-sys:console {
    deviate not-supported;
  }

  deviation /oc-sys:system/oc-sys:logging/oc-sys:files {
    deviate not-supported;
  }

  deviation /oc-sys:system/oc-sys:logging/oc-sys:vty {
    deviate not-supported;
  }

  deviation /oc-sys:system/oc-sys:messages/oc-sys:debug-entries {
    deviate not-supported;
  }

  deviation /oc-sys:system/oc-sys:memory {
    deviate not-supported;
  }

  deviation /oc-sys:system/oc-sys:cpus {
    deviate not-supported;
  }

  deviation /oc-sys:system/oc-sys:ntp/oc-sys:servers/oc-sys:server/oc-sys:config/oc-sys:port {
    deviate not-supported;
  }

  deviation /oc-sys:system/oc-sys:ntp/oc-sys:servers/oc-sys:server/oc-sys:config/oc-sys:prefer {
    deviate not-supported;
  }

  deviation /oc-sys:system/oc-sys:dns/oc-sys:servers {
    deviate not-supported;
  }

  deviation /oc-sys:system/oc-sys:dns/oc-sys:host-entries {
    deviate not-supported;
  }

  deviation /oc-sys:system/oc-sys:aaa/oc-sys:config {
    deviate not-supported;
  }

  deviation /oc-sys:system/oc-sys:aaa/oc-sys:state {
    deviate not-supported;
  }

  deviation /oc-sys:system/oc-sys:aaa/oc-sys:authorization/oc-sys:events {
    deviate not-supported;
  }

  deviation /oc-sys:system/oc-sys:aaa/oc-sys:accounting/oc-sys:events {
    deviate not-supported;
  }

  deviation /oc-sys:system/oc-sys:aaa/oc-sys:server-groups/oc-sys:server-group/oc-sys:servers/oc-sys:server/oc-sys:tacacs/oc-sys:config/oc-sys:secret-key-hashed {
    deviate not-supported;
  }

  deviation /oc-sys:system/oc-sys:aaa/oc-sys:server-groups/oc-sys:server-group/oc-sys:servers/oc-sys:server/oc-sys:radius/oc-sys:config/oc-sys:acct-port {
    deviate not-supported;
  }

  deviation /oc-sys:system/oc-sys:aaa/oc-sys:server-groups/oc-sys:server-group/oc-sys:servers/oc-sys:server/oc-sys:radius/oc-sys:config/oc-sys:secret-key-hashed {
    deviate not-supported;
  }

  deviation /oc-sys:system/oc-sys:alarms {
    deviate not-supported;
  }

  deviation /oc-sys:system/oc-sys:mount-points {
    deviate not-supported;
  }

  deviation /oc-sys:system/oc-sys:license {
    deviate not-supported;
  }

  deviation /oc-sys:system/oc-sys:mac-address {
    deviate not-supported;
  }

  deviation /oc-sys:system/oc-sys-util:utilization {
    deviate not-supported;
  }

  deviation /oc-sys:system/oc-hash:hashing {
    deviate not-supported;
  }

  deviation /oc-sys:system/oc-sys-bootz:bootz {
    deviate not-supported;
  }

  deviation /oc-intf:interfaces/oc-intf:interface/oc-intf:config/oc-hash:hashing-policy {
    deviate not-supported;
  }

  deviation /oc-intf:interfaces/oc-intf:interface/oc-intf:state/oc-hash:hashing-policy {
    deviate not-supported;
  }

}

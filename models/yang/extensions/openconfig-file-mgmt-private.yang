module openconfig-file-mgmt-private {

    yang-version "1";

    // namespace
    namespace "http://openconfig.net/yang/file-mgmt-private/extension";

    prefix "oc-file-mgmt-private";

    import openconfig-extensions { prefix oc-ext; }
    import openconfig-types { prefix "oc-types"; }

    organization "Dell";

    contact
      "Dell";

    description
      "This module describes deviation in file management model.";

    oc-ext:openconfig-version "0.0.1";

    revision "2021-10-01" {
      description
        "Minimal Copy Rpc.";
      reference "0.0.1";
    }

    typedef filename-uri-type {
       type string {
            pattern "((config|coredump|home|tech-support|ftp|http|scp|log):.*)" {
                error-message "Invalid folder name.";
            }
            pattern "running-configuration";
            pattern "startup-configuration";
       }

       description
            "Pattern for safe access to the file system";
    }

    grouping config-reload-state {
            description
               "Config Reload state";
            leaf state {
                type string;
                description "Config Reload State.";
            }
     }

    grouping config-reload-top {
       description "Top level grouping for config-reload containers.";
       container config-reload {
          description
              "Enclosing container for config-reload state data.";
          container state {
             config false;
             description
              "State information of Config Reload";
             uses config-reload-state;
          }
       }
    }
    uses config-reload-top;

    // rpc statements

    rpc copy {
        description
            "This procedure is used to copy a file from an external server to the switch, or from the switch to an external server.";
        input {
            leaf source {
                type filename-uri-type;
                description "Provide the filename in URI format for the source file.";
            }

            leaf destination {
                type filename-uri-type;
                description "Provide the filename in URI format for the destination file.";
            }

            leaf copy-config-option {
               type enumeration {
                  enum MERGE {
                     description
                        "The new configuration is merged to the running, i.e. 'config load'";
                  }
                  enum OVERWRITE {
                     description
                        "The new configuration is imported after all the services stop/restart, i.e. 'config reload'";
                  }
                  enum REPLACE {
                     description
                        "The new configuration replace the current running without the services stop/restart";
                  }
               }
               description
                  "The copy config options applicable only when destination is running-configuration";
            }

        }

        output {
            leaf status {
                type int32;
                description "The status of the operation execution request.";
            }
            leaf status-detail {
                type string;
                description "The detailed status of the operation execution request.";
            }
        }
    }
}
